Language="VBSCRIPT"

Sub CATMain()

Set partDocument1 = CATIA.ActiveDocument

Set part1 = partDocument1.Part

Set bodies1 = part1.Bodies

Set body1 = bodies1.Item("Hauptkörper")

Set sketches1 = body1.Sketches

Set reference1 = part1.CreateReferenceFromName("Selection_RSur:(Face:(Brp:(AxisSystem.2;1);None:();Cf12:());AxisSystem.2;Z0;G9061)")

Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 1.000000
arrayOfVariantOfDouble1(4) = 0.000000
arrayOfVariantOfDouble1(5) = 0.000000
arrayOfVariantOfDouble1(6) = 0.000000
arrayOfVariantOfDouble1(7) = 1.000000
arrayOfVariantOfDouble1(8) = 0.000000
sketch1.SetAbsoluteAxisData arrayOfVariantOfDouble1

part1.InWorkObject = sketch1

Set factory2D1 = sketch1.OpenEdition()

Set geometricElements1 = sketch1.GeometricElements

Set axis2D1 = geometricElements1.Item("Absolute Achse")

Set line2D1 = axis2D1.GetItem("H-Richtung")

line2D1.ReportName = 1

Set line2D2 = axis2D1.GetItem("V-Richtung")

line2D2.ReportName = 2

Set circle2D1 = factory2D1.CreateClosedCircle(0.000000, 0.000000, 5.000000)

Set point2D1 = axis2D1.GetItem("Ursprung")

circle2D1.CenterPoint = point2D1

circle2D1.ReportName = 3

Set constraints1 = sketch1.Constraints

Set reference2 = part1.CreateReferenceFromObject(circle2D1)

Set constraint1 = constraints1.AddMonoEltCst(catCstTypeRadius, reference2)

constraint1.Mode = catCstModeDrivingDimension

Set length1 = constraint1.Dimension

length1.Value = 5.000000

sketch1.CloseEdition 

part1.InWorkObject = sketch1

part1.Update 

Set shapeFactory1 = part1.ShapeFactory

Set pad1 = shapeFactory1.AddNewPad(sketch1, 6.400000)

Set limit1 = pad1.FirstLimit

Set length2 = limit1.Dimension

length2.Value = 45.000000

part1.Update 

Set reference3 = part1.CreateReferenceFromName("Selection_RSur:(Face:(Brp:(Pad.3;2);None:();Cf12:());Pad.3_ResultOUT;Z0;G9061)")

Set sketch2 = sketches1.Add(reference3)

Dim arrayOfVariantOfDouble2(8)
arrayOfVariantOfDouble2(0) = 0.000000
arrayOfVariantOfDouble2(1) = 0.000000
arrayOfVariantOfDouble2(2) = 45.000000
arrayOfVariantOfDouble2(3) = 1.000000
arrayOfVariantOfDouble2(4) = 0.000000
arrayOfVariantOfDouble2(5) = 0.000000
arrayOfVariantOfDouble2(6) = 0.000000
arrayOfVariantOfDouble2(7) = 1.000000
arrayOfVariantOfDouble2(8) = 0.000000
sketch2.SetAbsoluteAxisData arrayOfVariantOfDouble2

part1.InWorkObject = sketch2

Set factory2D2 = sketch2.OpenEdition()

Set geometricElements2 = sketch2.GeometricElements

Set axis2D2 = geometricElements2.Item("Absolute Achse")

Set line2D3 = axis2D2.GetItem("H-Richtung")

line2D3.ReportName = 1

Set line2D4 = axis2D2.GetItem("V-Richtung")

line2D4.ReportName = 2

Set point2D2 = factory2D2.CreatePoint(0.000000, -0.000000)

point2D2.ReportName = 3

Set point2D3 = factory2D2.CreatePoint(-7.707626, 4.450000)

point2D3.ReportName = 4

Set circle2D2 = factory2D2.CreateClosedCircle(0.000000, -0.000000, 10.276835)

circle2D2.CenterPoint = point2D2

circle2D2.ReportName = 5

circle2D2.Construction = True

Set circle2D3 = factory2D2.CreateClosedCircle(0.000000, -0.000000, 8.900000)

circle2D3.CenterPoint = point2D2

circle2D3.ReportName = 6

circle2D3.Construction = True

Set point2D4 = factory2D2.CreatePoint(-5.138417, 8.900000)

point2D4.ReportName = 7

Set point2D5 = factory2D2.CreatePoint(-10.276835, -0.000000)

point2D5.ReportName = 8

Set point2D6 = factory2D2.CreatePoint(-5.138417, -8.900000)

point2D6.ReportName = 9

Set point2D7 = factory2D2.CreatePoint(5.138417, -8.900000)

point2D7.ReportName = 10

Set point2D8 = factory2D2.CreatePoint(10.276835, -0.000000)

point2D8.ReportName = 11

Set point2D9 = factory2D2.CreatePoint(5.138417, 8.900000)

point2D9.ReportName = 12

Set line2D5 = factory2D2.CreateLine(-5.138417, 8.900000, -10.276835, -0.000000)

line2D5.ReportName = 13

line2D5.StartPoint = point2D4

line2D5.EndPoint = point2D5

Set line2D6 = factory2D2.CreateLine(-10.276835, -0.000000, -5.138417, -8.900000)

line2D6.ReportName = 14

line2D6.StartPoint = point2D5

line2D6.EndPoint = point2D6

Set line2D7 = factory2D2.CreateLine(-5.138417, -8.900000, 5.138417, -8.900000)

line2D7.ReportName = 15

line2D7.StartPoint = point2D6

line2D7.EndPoint = point2D7

Set line2D8 = factory2D2.CreateLine(5.138417, -8.900000, 10.276835, -0.000000)

line2D8.ReportName = 16

line2D8.StartPoint = point2D7

line2D8.EndPoint = point2D8

Set line2D9 = factory2D2.CreateLine(10.276835, -0.000000, 5.138417, 8.900000)

line2D9.ReportName = 17

line2D9.StartPoint = point2D8

line2D9.EndPoint = point2D9

Set line2D10 = factory2D2.CreateLine(5.138417, 8.900000, -5.138417, 8.900000)

line2D10.ReportName = 18

line2D10.StartPoint = point2D9

line2D10.EndPoint = point2D4

Set line2D11 = factory2D2.CreateLine(-0.000000, -0.000000, -7.707626, 4.450000)

line2D11.ReportName = 19

line2D11.Construction = True

line2D11.StartPoint = point2D2

line2D11.EndPoint = point2D3

Set constraints2 = sketch2.Constraints

Set reference4 = part1.CreateReferenceFromObject(circle2D2)

Set reference5 = part1.CreateReferenceFromObject(point2D4)

Set constraint2 = constraints2.AddBiEltCst(catCstTypeOn, reference4, reference5)

constraint2.Mode = catCstModeDrivingDimension

Set reference6 = part1.CreateReferenceFromObject(circle2D2)

Set reference7 = part1.CreateReferenceFromObject(point2D5)

Set constraint3 = constraints2.AddBiEltCst(catCstTypeOn, reference6, reference7)

constraint3.Mode = catCstModeDrivingDimension

Set reference8 = part1.CreateReferenceFromObject(circle2D2)

Set reference9 = part1.CreateReferenceFromObject(point2D6)

Set constraint4 = constraints2.AddBiEltCst(catCstTypeOn, reference8, reference9)

constraint4.Mode = catCstModeDrivingDimension

Set reference10 = part1.CreateReferenceFromObject(circle2D2)

Set reference11 = part1.CreateReferenceFromObject(point2D7)

Set constraint5 = constraints2.AddBiEltCst(catCstTypeOn, reference10, reference11)

constraint5.Mode = catCstModeDrivingDimension

Set reference12 = part1.CreateReferenceFromObject(circle2D2)

Set reference13 = part1.CreateReferenceFromObject(point2D8)

Set constraint6 = constraints2.AddBiEltCst(catCstTypeOn, reference12, reference13)

constraint6.Mode = catCstModeDrivingDimension

Set reference14 = part1.CreateReferenceFromObject(circle2D2)

Set reference15 = part1.CreateReferenceFromObject(point2D9)

Set constraint7 = constraints2.AddBiEltCst(catCstTypeOn, reference14, reference15)

constraint7.Mode = catCstModeDrivingDimension

Set reference16 = part1.CreateReferenceFromObject(circle2D3)

Set reference17 = part1.CreateReferenceFromObject(line2D5)

Set constraint8 = constraints2.AddBiEltCst(catCstTypeTangency, reference16, reference17)

constraint8.Mode = catCstModeDrivingDimension

Set reference18 = part1.CreateReferenceFromObject(circle2D3)

Set reference19 = part1.CreateReferenceFromObject(line2D6)

Set constraint9 = constraints2.AddBiEltCst(catCstTypeTangency, reference18, reference19)

constraint9.Mode = catCstModeDrivingDimension

Set reference20 = part1.CreateReferenceFromObject(circle2D3)

Set reference21 = part1.CreateReferenceFromObject(line2D7)

Set constraint10 = constraints2.AddBiEltCst(catCstTypeTangency, reference20, reference21)

constraint10.Mode = catCstModeDrivingDimension

Set reference22 = part1.CreateReferenceFromObject(circle2D3)

Set reference23 = part1.CreateReferenceFromObject(line2D8)

Set constraint11 = constraints2.AddBiEltCst(catCstTypeTangency, reference22, reference23)

constraint11.Mode = catCstModeDrivingDimension

Set reference24 = part1.CreateReferenceFromObject(circle2D3)

Set reference25 = part1.CreateReferenceFromObject(line2D9)

Set constraint12 = constraints2.AddBiEltCst(catCstTypeTangency, reference24, reference25)

constraint12.Mode = catCstModeDrivingDimension

Set reference26 = part1.CreateReferenceFromObject(circle2D3)

Set reference27 = part1.CreateReferenceFromObject(line2D10)

Set constraint13 = constraints2.AddBiEltCst(catCstTypeTangency, reference26, reference27)

constraint13.Mode = catCstModeDrivingDimension

Set reference28 = part1.CreateReferenceFromObject(point2D3)

Set reference29 = part1.CreateReferenceFromObject(line2D5)

Set constraint14 = constraints2.AddBiEltCst(catCstTypeMidPoint, reference28, reference29)

constraint14.Mode = catCstModeDrivingDimension

Set reference30 = part1.CreateReferenceFromObject(point2D2)

Set reference31 = part1.CreateReferenceFromObject(line2D4)

Set constraint15 = constraints2.AddBiEltCst(catCstTypeOn, reference30, reference31)

constraint15.Mode = catCstModeDrivingDimension

Set reference32 = part1.CreateReferenceFromObject(line2D3)

Set reference33 = part1.CreateReferenceFromObject(line2D10)

Set constraint16 = constraints2.AddBiEltCst(catCstTypeAngle, reference32, reference33)

constraint16.Mode = catCstModeDrivingDimension

constraint16.AngleSector = catCstAngleSector1

Set angle1 = constraint16.Dimension

angle1.Value = 0.000000

Set reference34 = part1.CreateReferenceFromObject(circle2D3)

Set constraint17 = constraints2.AddMonoEltCst(catCstTypeRadius, reference34)

constraint17.Mode = catCstModeDrivingDimension

Set length3 = constraint17.Dimension

length3.Value = 8.900000

Set reference35 = part1.CreateReferenceFromObject(point2D2)

Set reference36 = part1.CreateReferenceFromObject(line2D3)

Set constraint18 = constraints2.AddBiEltCst(catCstTypeOn, reference35, reference36)

constraint18.Mode = catCstModeDrivingDimension

sketch2.CloseEdition 

part1.InWorkObject = sketch2

part1.Update 

Set pad2 = shapeFactory1.AddNewPad(sketch2, 45.000000)

Set limit2 = pad2.FirstLimit

Set length4 = limit2.Dimension

length4.Value = 6.400000

part1.Update 

Set reference37 = part1.CreateReferenceFromName("Selection_RSur:(Face:(Brp:(AxisSystem.2;2);None:();Cf12:());AxisSystem.2;Z0;G9061)")

Set sketch3 = sketches1.Add(reference37)

Dim arrayOfVariantOfDouble3(8)
arrayOfVariantOfDouble3(0) = 0.000000
arrayOfVariantOfDouble3(1) = 0.000000
arrayOfVariantOfDouble3(2) = 0.000000
arrayOfVariantOfDouble3(3) = 0.000000
arrayOfVariantOfDouble3(4) = 1.000000
arrayOfVariantOfDouble3(5) = 0.000000
arrayOfVariantOfDouble3(6) = 0.000000
arrayOfVariantOfDouble3(7) = 0.000000
arrayOfVariantOfDouble3(8) = 1.000000
sketch3.SetAbsoluteAxisData arrayOfVariantOfDouble3

part1.InWorkObject = sketch3

Set factory2D3 = sketch3.OpenEdition()

Set geometricElements3 = sketch3.GeometricElements

Set axis2D3 = geometricElements3.Item("Absolute Achse")

Set line2D12 = axis2D3.GetItem("H-Richtung")

line2D12.ReportName = 1

Set line2D13 = axis2D3.GetItem("V-Richtung")

line2D13.ReportName = 2

Set point2D10 = factory2D3.CreatePoint(5.000000, 0.000000)

point2D10.ReportName = 3

point2D10.Construction = False

Set constraints3 = sketch3.Constraints

Set reference38 = part1.CreateReferenceFromObject(point2D10)

Set reference39 = part1.CreateReferenceFromObject(line2D12)

Set constraint19 = constraints3.AddBiEltCst(catCstTypeOn, reference38, reference39)

constraint19.Mode = catCstModeDrivingDimension

Set reference40 = part1.CreateReferenceFromObject(point2D10)

Set reference41 = part1.CreateReferenceFromObject(line2D13)

Set constraint20 = constraints3.AddBiEltCst(catCstTypeDistance, reference40, reference41)

constraint20.Mode = catCstModeDrivingDimension

Set length5 = constraint20.Dimension

length5.Value = 5.000000

sketch3.CloseEdition 

part1.InWorkObject = sketch3

part1.Update 

Set reference42 = part1.CreateReferenceFromObject(sketch3)

Set hybridShapeFactory1 = part1.HybridShapeFactory

Set axisSystems1 = part1.AxisSystems

Set axisSystem1 = axisSystems1.Item("Achsensystem.2")

Set reference43 = part1.CreateReferenceFromBRepName("REdge:(Edge:(Face:(Brp:(AxisSystem.2;3);None:();Cf12:());Face:(Brp:(AxisSystem.2;2);None:();Cf12:());None:(Limits1:();Limits2:());Cf12:());WithPermanentBody;WithoutBuildError;WithSelectingFeatureSupport;MFBRepVersion_CXR29)", axisSystem1)

Set hybridShapeHelix1 = hybridShapeFactory1.AddNewHelix(reference43, False, reference42, 1.000000, 10.000000, False, 0.000000, 0.000000, False)

hybridShapeHelix1.PitchLawType = 1

hybridShapeHelix1.SetStartingAngle 0.000000

hybridShapeHelix1.SetHeight 26.000000

body1.InsertHybridShape hybridShapeHelix1

part1.InWorkObject = hybridShapeHelix1

part1.Update 

Set reference44 = part1.CreateReferenceFromName("Selection_RSur:(Face:(Brp:(AxisSystem.2;2);None:();Cf12:());AxisSystem.2;Z0;G9061)")

Set sketch4 = sketches1.Add(reference44)

Dim arrayOfVariantOfDouble4(8)
arrayOfVariantOfDouble4(0) = 0.000000
arrayOfVariantOfDouble4(1) = 0.000000
arrayOfVariantOfDouble4(2) = 0.000000
arrayOfVariantOfDouble4(3) = 0.000000
arrayOfVariantOfDouble4(4) = 1.000000
arrayOfVariantOfDouble4(5) = 0.000000
arrayOfVariantOfDouble4(6) = 0.000000
arrayOfVariantOfDouble4(7) = 0.000000
arrayOfVariantOfDouble4(8) = 1.000000
sketch4.SetAbsoluteAxisData arrayOfVariantOfDouble4

part1.InWorkObject = sketch4

Set factory2D4 = sketch4.OpenEdition()

Set geometricElements4 = sketch4.GeometricElements

Set axis2D4 = geometricElements4.Item("Absolute Achse")

Set line2D14 = axis2D4.GetItem("H-Richtung")

line2D14.ReportName = 1

Set line2D15 = axis2D4.GetItem("V-Richtung")

line2D15.ReportName = 2

Set point2D11 = factory2D4.CreatePoint(5.000000, 0.000000)

point2D11.ReportName = 3

Set circle2D4 = factory2D4.CreateClosedCircle(5.000000, 0.000000, 0.500000)

circle2D4.CenterPoint = point2D11

circle2D4.ReportName = 4

Set reference45 = part1.CreateReferenceFromObject(sketch3)

Set geometricElements5 = factory2D4.CreateProjections(reference45)

Set geometry2D1 = geometricElements5.Item("Markierung.1")

geometry2D1.Construction = True

Set constraints4 = sketch4.Constraints

Set reference46 = part1.CreateReferenceFromObject(circle2D4)

Set constraint21 = constraints4.AddMonoEltCst(catCstTypeRadius, reference46)

constraint21.Mode = catCstModeDrivingDimension

Set length6 = constraint21.Dimension

length6.Value = 0.500000

Set reference47 = part1.CreateReferenceFromObject(geometry2D1)

Set reference48 = part1.CreateReferenceFromObject(point2D11)

Set constraint22 = constraints4.AddBiEltCst(catCstTypeOn, reference47, reference48)

constraint22.Mode = catCstModeDrivingDimension

sketch4.CloseEdition 

part1.InWorkObject = sketch4

part1.Update 

Set factory2D4 = sketch4.OpenEdition()

circle2D4.SetData 5.000000, 0.000000, 0.250000

length6.Value = 0.250000

sketch4.CloseEdition 

part1.InWorkObject = sketch4

part1.Update 

Set slot1 = shapeFactory1.AddNewSlotFromRef(Nothing, Nothing)

Set reference49 = part1.CreateReferenceFromObject(sketch4)

slot1.SetProfileElement reference49

Set reference50 = part1.CreateReferenceFromObject(hybridShapeHelix1)

slot1.CenterCurveElement = reference50

part1.Update 

End Sub
