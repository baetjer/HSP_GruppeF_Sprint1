Language="VBSCRIPT"

Sub CATMain()

Set partDocument1 = CATIA.ActiveDocument

Set part1 = partDocument1.Part

Set hybridBodies1 = part1.HybridBodies

Set hybridBody1 = hybridBodies1.Item("Geometrisches Set.1")

Set sketches1 = hybridBody1.HybridSketches

Set reference1 = part1.CreateReferenceFromName("Selection_RSur:(Face:(Brp:(AxisSystem.1;1);None:();Cf12:());AxisSystem.1;Z0;G9061)")

Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 1.000000
arrayOfVariantOfDouble1(4) = 0.000000
arrayOfVariantOfDouble1(5) = 0.000000
arrayOfVariantOfDouble1(6) = 0.000000
arrayOfVariantOfDouble1(7) = 1.000000
arrayOfVariantOfDouble1(8) = 0.000000
sketch1.SetAbsoluteAxisData arrayOfVariantOfDouble1

part1.InWorkObject = sketch1

Set factory2D1 = sketch1.OpenEdition()

Set geometricElements1 = sketch1.GeometricElements

Set axis2D1 = geometricElements1.Item("Absolute Achse")

Set line2D1 = axis2D1.GetItem("H-Richtung")

line2D1.ReportName = 1

Set line2D2 = axis2D1.GetItem("V-Richtung")

line2D2.ReportName = 2

Set circle2D1 = factory2D1.CreateClosedCircle(0.000000, 0.000000, 5.000000)

Set point2D1 = axis2D1.GetItem("Ursprung")

circle2D1.CenterPoint = point2D1

circle2D1.ReportName = 3

Set constraints1 = sketch1.Constraints

Set reference2 = part1.CreateReferenceFromObject(circle2D1)

Set constraint1 = constraints1.AddMonoEltCst(catCstTypeRadius, reference2)

constraint1.Mode = catCstModeDrivingDimension

Set length1 = constraint1.Dimension

length1.Value = 5.000000

sketch1.CloseEdition 

part1.InWorkObject = hybridBody1

part1.Update 

Set bodies1 = part1.Bodies

Set body1 = bodies1.Item("Hauptkörper")

part1.InWorkObject = body1

part1.InWorkObject = body1

Set shapeFactory1 = part1.ShapeFactory

Set pad1 = shapeFactory1.AddNewPad(sketch1, 20.000000)

Set limit1 = pad1.FirstLimit

Set length2 = limit1.Dimension

length2.Value = 45.000000

part1.Update 

Set sketches2 = body1.Sketches

Set reference3 = part1.CreateReferenceFromName("Selection_RSur:(Face:(Brp:(Pad.1;2);None:();Cf12:());Pad.1_ResultOUT;Z0;G9061)")

Set sketch2 = sketches2.Add(reference3)

Dim arrayOfVariantOfDouble2(8)
arrayOfVariantOfDouble2(0) = 0.000000
arrayOfVariantOfDouble2(1) = 0.000000
arrayOfVariantOfDouble2(2) = 45.000000
arrayOfVariantOfDouble2(3) = 1.000000
arrayOfVariantOfDouble2(4) = 0.000000
arrayOfVariantOfDouble2(5) = 0.000000
arrayOfVariantOfDouble2(6) = 0.000000
arrayOfVariantOfDouble2(7) = 1.000000
arrayOfVariantOfDouble2(8) = 0.000000
sketch2.SetAbsoluteAxisData arrayOfVariantOfDouble2

part1.InWorkObject = sketch2

Set factory2D2 = sketch2.OpenEdition()

Set geometricElements2 = sketch2.GeometricElements

Set axis2D2 = geometricElements2.Item("Absolute Achse")

Set line2D3 = axis2D2.GetItem("H-Richtung")

line2D3.ReportName = 1

Set line2D4 = axis2D2.GetItem("V-Richtung")

line2D4.ReportName = 2

Set circle2D2 = factory2D2.CreateClosedCircle(0.000000, 0.000000, 8.000000)

Set point2D2 = axis2D2.GetItem("Ursprung")

circle2D2.CenterPoint = point2D2

circle2D2.ReportName = 3

Set constraints2 = sketch2.Constraints

Set reference4 = part1.CreateReferenceFromObject(circle2D2)

Set constraint2 = constraints2.AddMonoEltCst(catCstTypeRadius, reference4)

constraint2.Mode = catCstModeDrivingDimension

Set length3 = constraint2.Dimension

length3.Value = 8.000000

sketch2.CloseEdition 

part1.InWorkObject = sketch2

part1.Update 

Set pad2 = shapeFactory1.AddNewPad(sketch2, 45.000000)

Set limit2 = pad2.FirstLimit

Set length4 = limit2.Dimension

length4.Value = 6.000000

part1.Update 

Set reference5 = part1.CreateReferenceFromName("Selection_RSur:(Face:(Brp:(Pad.2;2);None:();Cf12:());Pad.2_ResultOUT;Z0;G9061)")

Set sketch3 = sketches2.Add(reference5)

Dim arrayOfVariantOfDouble3(8)
arrayOfVariantOfDouble3(0) = 0.000000
arrayOfVariantOfDouble3(1) = 0.000000
arrayOfVariantOfDouble3(2) = 51.000000
arrayOfVariantOfDouble3(3) = 1.000000
arrayOfVariantOfDouble3(4) = 0.000000
arrayOfVariantOfDouble3(5) = 0.000000
arrayOfVariantOfDouble3(6) = 0.000000
arrayOfVariantOfDouble3(7) = 1.000000
arrayOfVariantOfDouble3(8) = 0.000000
sketch3.SetAbsoluteAxisData arrayOfVariantOfDouble3

part1.InWorkObject = sketch3

Set factory2D3 = sketch3.OpenEdition()

Set geometricElements3 = sketch3.GeometricElements

Set axis2D3 = geometricElements3.Item("Absolute Achse")

Set line2D5 = axis2D3.GetItem("H-Richtung")

line2D5.ReportName = 1

Set line2D6 = axis2D3.GetItem("V-Richtung")

line2D6.ReportName = 2

Set point2D3 = factory2D3.CreatePoint(-10.000000, 1.250000)

point2D3.ReportName = 3

Set point2D4 = factory2D3.CreatePoint(10.000000, 1.250000)

point2D4.ReportName = 4

Set line2D7 = factory2D3.CreateLine(-10.000000, 1.250000, 10.000000, 1.250000)

line2D7.ReportName = 5

line2D7.StartPoint = point2D3

line2D7.EndPoint = point2D4

Set point2D5 = factory2D3.CreatePoint(10.000000, -1.250000)

point2D5.ReportName = 6

Set line2D8 = factory2D3.CreateLine(10.000000, 1.250000, 10.000000, -1.250000)

line2D8.ReportName = 7

line2D8.EndPoint = point2D4

line2D8.StartPoint = point2D5

Set point2D6 = factory2D3.CreatePoint(-10.000000, -1.250000)

point2D6.ReportName = 8

Set line2D9 = factory2D3.CreateLine(10.000000, -1.250000, -10.000000, -1.250000)

line2D9.ReportName = 9

line2D9.StartPoint = point2D5

line2D9.EndPoint = point2D6

Set line2D10 = factory2D3.CreateLine(-10.000000, -1.250000, -10.000000, 1.250000)

line2D10.ReportName = 10

line2D10.EndPoint = point2D6

line2D10.StartPoint = point2D3

Set constraints3 = sketch3.Constraints

Set reference6 = part1.CreateReferenceFromObject(line2D7)

Set reference7 = part1.CreateReferenceFromObject(line2D5)

Set constraint3 = constraints3.AddBiEltCst(catCstTypeHorizontality, reference6, reference7)

constraint3.Mode = catCstModeDrivingDimension

Set reference8 = part1.CreateReferenceFromObject(line2D9)

Set reference9 = part1.CreateReferenceFromObject(line2D5)

Set constraint4 = constraints3.AddBiEltCst(catCstTypeHorizontality, reference8, reference9)

constraint4.Mode = catCstModeDrivingDimension

Set reference10 = part1.CreateReferenceFromObject(line2D8)

Set reference11 = part1.CreateReferenceFromObject(line2D6)

Set constraint5 = constraints3.AddBiEltCst(catCstTypeVerticality, reference10, reference11)

constraint5.Mode = catCstModeDrivingDimension

Set reference12 = part1.CreateReferenceFromObject(line2D10)

Set reference13 = part1.CreateReferenceFromObject(line2D6)

Set constraint6 = constraints3.AddBiEltCst(catCstTypeVerticality, reference12, reference13)

constraint6.Mode = catCstModeDrivingDimension

Set reference14 = part1.CreateReferenceFromObject(line2D8)

Set constraint7 = constraints3.AddMonoEltCst(catCstTypeLength, reference14)

constraint7.Mode = catCstModeDrivingDimension

Set length5 = constraint7.Dimension

length5.Value = 2.500000

Set reference15 = part1.CreateReferenceFromObject(line2D7)

Set constraint8 = constraints3.AddMonoEltCst(catCstTypeLength, reference15)

constraint8.Mode = catCstModeDrivingDimension

Set length6 = constraint8.Dimension

length6.Value = 20.000000

Set reference16 = part1.CreateReferenceFromObject(line2D6)

Set reference17 = part1.CreateReferenceFromObject(line2D10)

Set constraint9 = constraints3.AddBiEltCst(catCstTypeDistance, reference16, reference17)

constraint9.Mode = catCstModeDrivingDimension

Set length7 = constraint9.Dimension

length7.Value = 10.000000

Set reference18 = part1.CreateReferenceFromObject(line2D9)

Set reference19 = part1.CreateReferenceFromObject(line2D5)

Set constraint10 = constraints3.AddBiEltCst(catCstTypeDistance, reference18, reference19)

constraint10.Mode = catCstModeDrivingDimension

Set length8 = constraint10.Dimension

length8.Value = 1.250000

sketch3.CloseEdition 

part1.InWorkObject = sketch3

part1.Update 

Set pocket1 = shapeFactory1.AddNewPocket(sketch3, 6.000000)

pocket1.DirectionOrientation = catRegularOrientation

Set limit3 = pocket1.FirstLimit

Set length9 = limit3.Dimension

length9.Value = 2.400000

part1.Update 

pocket1.DirectionOrientation = catInverseOrientation

part1.Update 

Set reference20 = part1.CreateReferenceFromName("Selection_RSur:(Face:(Brp:(AxisSystem.1;2);None:();Cf12:());AxisSystem.1;Z0;G9061)")

Set sketch4 = sketches2.Add(reference20)

Dim arrayOfVariantOfDouble4(8)
arrayOfVariantOfDouble4(0) = 0.000000
arrayOfVariantOfDouble4(1) = 0.000000
arrayOfVariantOfDouble4(2) = 0.000000
arrayOfVariantOfDouble4(3) = 0.000000
arrayOfVariantOfDouble4(4) = 1.000000
arrayOfVariantOfDouble4(5) = 0.000000
arrayOfVariantOfDouble4(6) = 0.000000
arrayOfVariantOfDouble4(7) = 0.000000
arrayOfVariantOfDouble4(8) = 1.000000
sketch4.SetAbsoluteAxisData arrayOfVariantOfDouble4

part1.InWorkObject = sketch4

Set factory2D4 = sketch4.OpenEdition()

Set geometricElements4 = sketch4.GeometricElements

Set axis2D4 = geometricElements4.Item("Absolute Achse")

Set line2D11 = axis2D4.GetItem("H-Richtung")

line2D11.ReportName = 1

Set line2D12 = axis2D4.GetItem("V-Richtung")

line2D12.ReportName = 2

Set point2D7 = factory2D4.CreatePoint(5.000000, 0.000000)

point2D7.ReportName = 3

point2D7.Construction = False

Set constraints4 = sketch4.Constraints

Set reference21 = part1.CreateReferenceFromObject(point2D7)

Set reference22 = part1.CreateReferenceFromObject(line2D11)

Set constraint11 = constraints4.AddBiEltCst(catCstTypeOn, reference21, reference22)

constraint11.Mode = catCstModeDrivingDimension

Set reference23 = part1.CreateReferenceFromObject(point2D7)

Set reference24 = part1.CreateReferenceFromObject(line2D12)

Set constraint12 = constraints4.AddBiEltCst(catCstTypeDistance, reference23, reference24)

constraint12.Mode = catCstModeDrivingDimension

Set length10 = constraint12.Dimension

length10.Value = 5.000000

sketch4.CloseEdition 

part1.InWorkObject = sketch4

part1.Update 

Set reference25 = part1.CreateReferenceFromObject(sketch4)

Set hybridShapeFactory1 = part1.HybridShapeFactory

Set reference26 = axis2D4.GetItem("V-Richtung")

Set hybridShapeHelix1 = hybridShapeFactory1.AddNewHelix(reference26, False, reference25, 1.000000, 10.000000, False, 0.000000, 0.000000, False)

hybridShapeHelix1.PitchLawType = 1

hybridShapeHelix1.SetStartingAngle 0.000000

hybridShapeHelix1.SetHeight 32.000000

body1.InsertHybridShape hybridShapeHelix1

part1.InWorkObject = hybridShapeHelix1

part1.Update 

Set reference27 = part1.CreateReferenceFromObject(sketch4)

Set hybridShapeHelix1 = hybridShapeFactory1.AddNewHelix(reference26, False, reference27, 1.000000, 10.000000, False, 0.000000, 0.000000, False)

hybridShapeHelix1.PitchLawType = 1

hybridShapeHelix1.SetStartingAngle 0.000000

hybridShapeHelix1.SetHeight 38.000000

body1.InsertHybridShape hybridShapeHelix1

part1.InWorkObject = hybridShapeHelix1

part1.Update 

Set reference28 = part1.CreateReferenceFromName("Selection_RSur:(Face:(Brp:(AxisSystem.1;2);None:();Cf12:());AxisSystem.1;Z0;G9061)")

Set sketch5 = sketches2.Add(reference28)

Dim arrayOfVariantOfDouble5(8)
arrayOfVariantOfDouble5(0) = 0.000000
arrayOfVariantOfDouble5(1) = 0.000000
arrayOfVariantOfDouble5(2) = 0.000000
arrayOfVariantOfDouble5(3) = 0.000000
arrayOfVariantOfDouble5(4) = 1.000000
arrayOfVariantOfDouble5(5) = 0.000000
arrayOfVariantOfDouble5(6) = 0.000000
arrayOfVariantOfDouble5(7) = 0.000000
arrayOfVariantOfDouble5(8) = 1.000000
sketch5.SetAbsoluteAxisData arrayOfVariantOfDouble5

part1.InWorkObject = sketch5

Set factory2D5 = sketch5.OpenEdition()

Set geometricElements5 = sketch5.GeometricElements

Set axis2D5 = geometricElements5.Item("Absolute Achse")

Set line2D13 = axis2D5.GetItem("H-Richtung")

line2D13.ReportName = 1

Set line2D14 = axis2D5.GetItem("V-Richtung")

line2D14.ReportName = 2

Set point2D8 = factory2D5.CreatePoint(5.000000, 0.000000)

point2D8.ReportName = 3

Set circle2D3 = factory2D5.CreateClosedCircle(5.000000, 0.000000, 0.250000)

circle2D3.CenterPoint = point2D8

circle2D3.ReportName = 4

Set reference29 = part1.CreateReferenceFromObject(sketch4)

Set geometricElements6 = factory2D5.CreateProjections(reference29)

Set geometry2D1 = geometricElements6.Item("Markierung.1")

geometry2D1.Construction = True

Set constraints5 = sketch5.Constraints

Set reference30 = part1.CreateReferenceFromObject(circle2D3)

Set constraint13 = constraints5.AddMonoEltCst(catCstTypeRadius, reference30)

constraint13.Mode = catCstModeDrivingDimension

Set length11 = constraint13.Dimension

length11.Value = 0.250000

Set reference31 = part1.CreateReferenceFromObject(point2D8)

Set reference32 = part1.CreateReferenceFromObject(geometry2D1)

Set constraint14 = constraints5.AddBiEltCst(catCstTypeOn, reference31, reference32)

constraint14.Mode = catCstModeDrivingDimension

sketch5.CloseEdition 

part1.InWorkObject = sketch5

part1.Update 

Set slot1 = shapeFactory1.AddNewSlotFromRef(Nothing, Nothing)

Set reference33 = part1.CreateReferenceFromObject(sketch5)

slot1.SetProfileElement reference33

Set reference34 = part1.CreateReferenceFromObject(hybridShapeHelix1)

slot1.CenterCurveElement = reference34

part1.Update 

End Sub
