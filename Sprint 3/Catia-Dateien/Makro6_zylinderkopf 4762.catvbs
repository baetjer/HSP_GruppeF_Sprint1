Language="VBSCRIPT"

Sub CATMain()

Set partDocument1 = CATIA.ActiveDocument

Set part1 = partDocument1.Part

Set hybridBodies1 = part1.HybridBodies

Set hybridBody1 = hybridBodies1.Item("Geometrisches Set.1")

Set sketches1 = hybridBody1.HybridSketches

Set reference1 = part1.CreateReferenceFromName("Selection_RSur:(Face:(Brp:(AxisSystem.1;1);None:();Cf12:());AxisSystem.1;Z0;G9061)")

Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 1.000000
arrayOfVariantOfDouble1(4) = 0.000000
arrayOfVariantOfDouble1(5) = 0.000000
arrayOfVariantOfDouble1(6) = 0.000000
arrayOfVariantOfDouble1(7) = 1.000000
arrayOfVariantOfDouble1(8) = 0.000000
sketch1.SetAbsoluteAxisData arrayOfVariantOfDouble1

part1.InWorkObject = sketch1

Set factory2D1 = sketch1.OpenEdition()

Set geometricElements1 = sketch1.GeometricElements

Set axis2D1 = geometricElements1.Item("Absolute Achse")

Set line2D1 = axis2D1.GetItem("H-Richtung")

line2D1.ReportName = 1

Set line2D2 = axis2D1.GetItem("V-Richtung")

line2D2.ReportName = 2

Set circle2D1 = factory2D1.CreateClosedCircle(0.000000, 0.000000, 8.000000)

Set point2D1 = axis2D1.GetItem("Ursprung")

circle2D1.CenterPoint = point2D1

circle2D1.ReportName = 3

Set constraints1 = sketch1.Constraints

Set reference2 = part1.CreateReferenceFromObject(circle2D1)

Set constraint1 = constraints1.AddMonoEltCst(catCstTypeRadius, reference2)

constraint1.Mode = catCstModeDrivingDimension

Set length1 = constraint1.Dimension

length1.Value = 8.000000

sketch1.CloseEdition 

part1.InWorkObject = hybridBody1

part1.Update 

Set bodies1 = part1.Bodies

Set body1 = bodies1.Item("Hauptkörper")

part1.InWorkObject = body1

part1.InWorkObject = body1

Set shapeFactory1 = part1.ShapeFactory

Set pad1 = shapeFactory1.AddNewPad(sketch1, 20.000000)

Set limit1 = pad1.FirstLimit

Set length2 = limit1.Dimension

length2.Value = 10.000000

part1.Update 

Set sketches2 = body1.Sketches

Set reference3 = part1.CreateReferenceFromName("Selection_RSur:(Face:(Brp:(Pad.1;2);None:();Cf12:());Pad.1_ResultOUT;Z0;G9061)")

Set sketch2 = sketches2.Add(reference3)

Dim arrayOfVariantOfDouble2(8)
arrayOfVariantOfDouble2(0) = 0.000000
arrayOfVariantOfDouble2(1) = 0.000000
arrayOfVariantOfDouble2(2) = 10.000000
arrayOfVariantOfDouble2(3) = 1.000000
arrayOfVariantOfDouble2(4) = 0.000000
arrayOfVariantOfDouble2(5) = 0.000000
arrayOfVariantOfDouble2(6) = 0.000000
arrayOfVariantOfDouble2(7) = 1.000000
arrayOfVariantOfDouble2(8) = 0.000000
sketch2.SetAbsoluteAxisData arrayOfVariantOfDouble2

part1.InWorkObject = sketch2

Set factory2D2 = sketch2.OpenEdition()

Set geometricElements2 = sketch2.GeometricElements

Set axis2D2 = geometricElements2.Item("Absolute Achse")

Set line2D3 = axis2D2.GetItem("H-Richtung")

line2D3.ReportName = 1

Set line2D4 = axis2D2.GetItem("V-Richtung")

line2D4.ReportName = 2

Set point2D2 = factory2D2.CreatePoint(0.000000, -4.000000)

point2D2.ReportName = 3

Set circle2D2 = factory2D2.CreateClosedCircle(0.000000, 0.000000, 4.618802)

Set point2D3 = axis2D2.GetItem("Ursprung")

circle2D2.CenterPoint = point2D3

circle2D2.ReportName = 4

circle2D2.Construction = True

Set circle2D3 = factory2D2.CreateClosedCircle(0.000000, 0.000000, 4.000000)

circle2D3.CenterPoint = point2D3

circle2D3.ReportName = 5

circle2D3.Construction = True

Set point2D4 = factory2D2.CreatePoint(-2.309401, -4.000000)

point2D4.ReportName = 6

Set point2D5 = factory2D2.CreatePoint(2.309401, -4.000000)

point2D5.ReportName = 7

Set point2D6 = factory2D2.CreatePoint(4.618802, 0.000000)

point2D6.ReportName = 8

Set point2D7 = factory2D2.CreatePoint(2.309401, 4.000000)

point2D7.ReportName = 9

Set point2D8 = factory2D2.CreatePoint(-2.309401, 4.000000)

point2D8.ReportName = 10

Set point2D9 = factory2D2.CreatePoint(-4.618802, 0.000000)

point2D9.ReportName = 11

Set line2D5 = factory2D2.CreateLine(-2.309401, -4.000000, 2.309401, -4.000000)

line2D5.ReportName = 12

line2D5.StartPoint = point2D4

line2D5.EndPoint = point2D5

Set line2D6 = factory2D2.CreateLine(2.309401, -4.000000, 4.618802, -0.000000)

line2D6.ReportName = 13

line2D6.StartPoint = point2D5

line2D6.EndPoint = point2D6

Set line2D7 = factory2D2.CreateLine(4.618802, 0.000000, 2.309401, 4.000000)

line2D7.ReportName = 14

line2D7.StartPoint = point2D6

line2D7.EndPoint = point2D7

Set line2D8 = factory2D2.CreateLine(2.309401, 4.000000, -2.309401, 4.000000)

line2D8.ReportName = 15

line2D8.StartPoint = point2D7

line2D8.EndPoint = point2D8

Set line2D9 = factory2D2.CreateLine(-2.309401, 4.000000, -4.618802, 0.000000)

line2D9.ReportName = 16

line2D9.StartPoint = point2D8

line2D9.EndPoint = point2D9

Set line2D10 = factory2D2.CreateLine(-4.618802, 0.000000, -2.309401, -4.000000)

line2D10.ReportName = 17

line2D10.StartPoint = point2D9

line2D10.EndPoint = point2D4

Set line2D11 = factory2D2.CreateLine(0.000000, 0.000000, 0.000000, -4.000000)

line2D11.ReportName = 18

line2D11.Construction = True

line2D11.StartPoint = point2D3

line2D11.EndPoint = point2D2

Set constraints2 = sketch2.Constraints

Set reference4 = part1.CreateReferenceFromObject(circle2D2)

Set reference5 = part1.CreateReferenceFromObject(point2D4)

Set constraint2 = constraints2.AddBiEltCst(catCstTypeOn, reference4, reference5)

constraint2.Mode = catCstModeDrivingDimension

Set reference6 = part1.CreateReferenceFromObject(circle2D2)

Set reference7 = part1.CreateReferenceFromObject(point2D5)

Set constraint3 = constraints2.AddBiEltCst(catCstTypeOn, reference6, reference7)

constraint3.Mode = catCstModeDrivingDimension

Set reference8 = part1.CreateReferenceFromObject(circle2D2)

Set reference9 = part1.CreateReferenceFromObject(point2D6)

Set constraint4 = constraints2.AddBiEltCst(catCstTypeOn, reference8, reference9)

constraint4.Mode = catCstModeDrivingDimension

Set reference10 = part1.CreateReferenceFromObject(circle2D2)

Set reference11 = part1.CreateReferenceFromObject(point2D7)

Set constraint5 = constraints2.AddBiEltCst(catCstTypeOn, reference10, reference11)

constraint5.Mode = catCstModeDrivingDimension

Set reference12 = part1.CreateReferenceFromObject(circle2D2)

Set reference13 = part1.CreateReferenceFromObject(point2D8)

Set constraint6 = constraints2.AddBiEltCst(catCstTypeOn, reference12, reference13)

constraint6.Mode = catCstModeDrivingDimension

Set reference14 = part1.CreateReferenceFromObject(circle2D2)

Set reference15 = part1.CreateReferenceFromObject(point2D9)

Set constraint7 = constraints2.AddBiEltCst(catCstTypeOn, reference14, reference15)

constraint7.Mode = catCstModeDrivingDimension

Set reference16 = part1.CreateReferenceFromObject(circle2D3)

Set reference17 = part1.CreateReferenceFromObject(line2D5)

Set constraint8 = constraints2.AddBiEltCst(catCstTypeTangency, reference16, reference17)

constraint8.Mode = catCstModeDrivingDimension

Set reference18 = part1.CreateReferenceFromObject(circle2D3)

Set reference19 = part1.CreateReferenceFromObject(line2D6)

Set constraint9 = constraints2.AddBiEltCst(catCstTypeTangency, reference18, reference19)

constraint9.Mode = catCstModeDrivingDimension

Set reference20 = part1.CreateReferenceFromObject(circle2D3)

Set reference21 = part1.CreateReferenceFromObject(line2D7)

Set constraint10 = constraints2.AddBiEltCst(catCstTypeTangency, reference20, reference21)

constraint10.Mode = catCstModeDrivingDimension

Set reference22 = part1.CreateReferenceFromObject(circle2D3)

Set reference23 = part1.CreateReferenceFromObject(line2D8)

Set constraint11 = constraints2.AddBiEltCst(catCstTypeTangency, reference22, reference23)

constraint11.Mode = catCstModeDrivingDimension

Set reference24 = part1.CreateReferenceFromObject(circle2D3)

Set reference25 = part1.CreateReferenceFromObject(line2D9)

Set constraint12 = constraints2.AddBiEltCst(catCstTypeTangency, reference24, reference25)

constraint12.Mode = catCstModeDrivingDimension

Set reference26 = part1.CreateReferenceFromObject(circle2D3)

Set reference27 = part1.CreateReferenceFromObject(line2D10)

Set constraint13 = constraints2.AddBiEltCst(catCstTypeTangency, reference26, reference27)

constraint13.Mode = catCstModeDrivingDimension

Set reference28 = part1.CreateReferenceFromObject(point2D2)

Set reference29 = part1.CreateReferenceFromObject(line2D5)

Set constraint14 = constraints2.AddBiEltCst(catCstTypeMidPoint, reference28, reference29)

constraint14.Mode = catCstModeDrivingDimension

Set reference30 = part1.CreateReferenceFromObject(line2D11)

Set reference31 = part1.CreateReferenceFromObject(line2D4)

Set constraint15 = constraints2.AddBiEltCst(catCstTypeVerticality, reference30, reference31)

constraint15.Mode = catCstModeDrivingDimension

Set reference32 = part1.CreateReferenceFromObject(circle2D3)

Set constraint16 = constraints2.AddMonoEltCst(catCstTypeRadius, reference32)

constraint16.Mode = catCstModeDrivingDimension

Set length3 = constraint16.Dimension

length3.Value = 4.000000

sketch2.CloseEdition 

part1.InWorkObject = sketch2

part1.Update 

Set pocket1 = shapeFactory1.AddNewPocket(sketch2, 10.000000)

Set limit2 = pocket1.FirstLimit

Set length4 = limit2.Dimension

length4.Value = 4.000000

part1.Update 

length4.Value = 6.000000

part1.Update 

End Sub
