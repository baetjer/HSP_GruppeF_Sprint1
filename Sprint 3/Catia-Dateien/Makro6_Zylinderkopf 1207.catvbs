Language="VBSCRIPT"

Sub CATMain()

Set partDocument1 = CATIA.ActiveDocument

Set part1 = partDocument1.Part

Set bodies1 = part1.Bodies

Set body1 = bodies1.Item("Hauptkörper")

Set sketches1 = body1.Sketches

Set reference1 = part1.CreateReferenceFromName("Selection_RSur:(Face:(Brp:(AxisSystem.2;1);None:();Cf12:());AxisSystem.2;Z0;G9061)")

Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 1.000000
arrayOfVariantOfDouble1(4) = 0.000000
arrayOfVariantOfDouble1(5) = 0.000000
arrayOfVariantOfDouble1(6) = 0.000000
arrayOfVariantOfDouble1(7) = 1.000000
arrayOfVariantOfDouble1(8) = 0.000000
sketch1.SetAbsoluteAxisData arrayOfVariantOfDouble1

part1.InWorkObject = sketch1

Set factory2D1 = sketch1.OpenEdition()

Set geometricElements1 = sketch1.GeometricElements

Set axis2D1 = geometricElements1.Item("Absolute Achse")

Set line2D1 = axis2D1.GetItem("H-Richtung")

line2D1.ReportName = 1

Set line2D2 = axis2D1.GetItem("V-Richtung")

line2D2.ReportName = 2

Set circle2D1 = factory2D1.CreateClosedCircle(0.000000, 0.000000, 8.000000)

Set point2D1 = axis2D1.GetItem("Ursprung")

circle2D1.CenterPoint = point2D1

circle2D1.ReportName = 3

Set constraints1 = sketch1.Constraints

Set reference2 = part1.CreateReferenceFromObject(circle2D1)

Set constraint1 = constraints1.AddMonoEltCst(catCstTypeRadius, reference2)

constraint1.Mode = catCstModeDrivingDimension

Set length1 = constraint1.Dimension

length1.Value = 8.000000

sketch1.CloseEdition 

part1.InWorkObject = sketch1

part1.Update 

Set shapeFactory1 = part1.ShapeFactory

Set pad1 = shapeFactory1.AddNewPad(sketch1, 6.000000)

part1.Update 

Set reference3 = part1.CreateReferenceFromName("Selection_RSur:(Face:(Brp:(Pad.2;2);None:();Cf12:());Pad.2_ResultOUT;Z0;G9061)")

Set sketch2 = sketches1.Add(reference3)

Dim arrayOfVariantOfDouble2(8)
arrayOfVariantOfDouble2(0) = 0.000000
arrayOfVariantOfDouble2(1) = 0.000000
arrayOfVariantOfDouble2(2) = 6.000000
arrayOfVariantOfDouble2(3) = 1.000000
arrayOfVariantOfDouble2(4) = 0.000000
arrayOfVariantOfDouble2(5) = 0.000000
arrayOfVariantOfDouble2(6) = 0.000000
arrayOfVariantOfDouble2(7) = 1.000000
arrayOfVariantOfDouble2(8) = 0.000000
sketch2.SetAbsoluteAxisData arrayOfVariantOfDouble2

part1.InWorkObject = sketch2

Set factory2D2 = sketch2.OpenEdition()

Set geometricElements2 = sketch2.GeometricElements

Set axis2D2 = geometricElements2.Item("Absolute Achse")

Set line2D3 = axis2D2.GetItem("H-Richtung")

line2D3.ReportName = 1

Set line2D4 = axis2D2.GetItem("V-Richtung")

line2D4.ReportName = 2

Set point2D2 = factory2D2.CreatePoint(-9.000000, 1.250000)

point2D2.ReportName = 3

Set point2D3 = factory2D2.CreatePoint(9.000000, 1.250000)

point2D3.ReportName = 4

Set line2D5 = factory2D2.CreateLine(-9.000000, 1.250000, 9.000000, 1.250000)

line2D5.ReportName = 5

line2D5.StartPoint = point2D2

line2D5.EndPoint = point2D3

Set point2D4 = factory2D2.CreatePoint(9.000000, -1.250000)

point2D4.ReportName = 6

Set line2D6 = factory2D2.CreateLine(9.000000, 1.250000, 9.000000, -1.250000)

line2D6.ReportName = 7

line2D6.EndPoint = point2D3

line2D6.StartPoint = point2D4

Set point2D5 = factory2D2.CreatePoint(-9.000000, -1.250000)

point2D5.ReportName = 8

Set line2D7 = factory2D2.CreateLine(9.000000, -1.250000, -9.000000, -1.250000)

line2D7.ReportName = 9

line2D7.StartPoint = point2D4

line2D7.EndPoint = point2D5

Set line2D8 = factory2D2.CreateLine(-9.000000, -1.250000, -9.000000, 1.250000)

line2D8.ReportName = 10

line2D8.EndPoint = point2D5

line2D8.StartPoint = point2D2

Set axisSystems1 = part1.AxisSystems

Set axisSystem1 = axisSystems1.Item("Achsensystem.2")

Set reference4 = part1.CreateReferenceFromBRepName("FEdge:(Edge:(Face:(Brp:(AxisSystem.2;2);None:();Cf12:());Face:(Brp:(AxisSystem.2;1);None:();Cf12:());None:(Limits1:();Limits2:());Cf12:());WithPermanentBody;WithoutBuildError;WithInitialFeatureSupport;MonoFond;MFBRepVersion_CXR29)", axisSystem1)

Set geometricElements3 = factory2D2.CreateProjections(reference4)

Set geometry2D1 = geometricElements3.Item("Markierung.1")

geometry2D1.Construction = True

Set constraints2 = sketch2.Constraints

Set reference5 = part1.CreateReferenceFromObject(line2D5)

Set reference6 = part1.CreateReferenceFromObject(line2D3)

Set constraint2 = constraints2.AddBiEltCst(catCstTypeHorizontality, reference5, reference6)

constraint2.Mode = catCstModeDrivingDimension

Set reference7 = part1.CreateReferenceFromObject(line2D7)

Set reference8 = part1.CreateReferenceFromObject(line2D3)

Set constraint3 = constraints2.AddBiEltCst(catCstTypeHorizontality, reference7, reference8)

constraint3.Mode = catCstModeDrivingDimension

Set reference9 = part1.CreateReferenceFromObject(line2D6)

Set reference10 = part1.CreateReferenceFromObject(line2D4)

Set constraint4 = constraints2.AddBiEltCst(catCstTypeVerticality, reference9, reference10)

constraint4.Mode = catCstModeDrivingDimension

Set reference11 = part1.CreateReferenceFromObject(line2D8)

Set reference12 = part1.CreateReferenceFromObject(line2D4)

Set constraint5 = constraints2.AddBiEltCst(catCstTypeVerticality, reference11, reference12)

constraint5.Mode = catCstModeDrivingDimension

Set reference13 = part1.CreateReferenceFromObject(line2D5)

Set constraint6 = constraints2.AddMonoEltCst(catCstTypeLength, reference13)

constraint6.Mode = catCstModeDrivingDimension

Set length2 = constraint6.Dimension

length2.Value = 18.000000

Set reference14 = part1.CreateReferenceFromObject(line2D6)

Set constraint7 = constraints2.AddMonoEltCst(catCstTypeLength, reference14)

constraint7.Mode = catCstModeDrivingDimension

Set length3 = constraint7.Dimension

length3.Value = 2.500000

Set reference15 = part1.CreateReferenceFromObject(line2D3)

Set reference16 = part1.CreateReferenceFromObject(line2D7)

Set constraint8 = constraints2.AddBiEltCst(catCstTypeDistance, reference15, reference16)

constraint8.Mode = catCstModeDrivingDimension

Set length4 = constraint8.Dimension

length4.Value = 1.250000

Set reference17 = part1.CreateReferenceFromObject(line2D6)

Set reference18 = part1.CreateReferenceFromObject(geometry2D1)

Set constraint9 = constraints2.AddBiEltCst(catCstTypeDistance, reference17, reference18)

constraint9.Mode = catCstModeDrivingDimension

Set length5 = constraint9.Dimension

length5.Value = 9.000000

sketch2.CloseEdition 

part1.InWorkObject = sketch2

part1.Update 

length4.Value = 1.250000

length5.Value = 9.000000

Set reference19 = part1.CreateReferenceFromName("")

Set pocket1 = shapeFactory1.AddNewPocketFromRef(reference19, 6.000000)

Set limit1 = pocket1.FirstLimit

Set length6 = limit1.Dimension

length6.Value = 2.400000

Set reference20 = part1.CreateReferenceFromObject(sketch2)

pocket1.SetProfileElement reference20

part1.Update 

End Sub
