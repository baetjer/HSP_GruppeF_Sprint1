Language="VBSCRIPT"

Sub CATMain()

Set partDocument1 = CATIA.ActiveDocument

Set part1 = partDocument1.Part

Set hybridBodies1 = part1.HybridBodies

Set hybridBody1 = hybridBodies1.Item("Geometrisches Set.1")

Set sketches1 = hybridBody1.HybridSketches

Set reference1 = part1.CreateReferenceFromName("Selection_RSur:(Face:(Brp:(AxisSystem.2;2);None:();Cf12:());AxisSystem.2;Z0;G9061)")

Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 0.000000
arrayOfVariantOfDouble1(4) = 1.000000
arrayOfVariantOfDouble1(5) = 0.000000
arrayOfVariantOfDouble1(6) = 0.000000
arrayOfVariantOfDouble1(7) = 0.000000
arrayOfVariantOfDouble1(8) = 1.000000
sketch1.SetAbsoluteAxisData arrayOfVariantOfDouble1

part1.InWorkObject = sketch1

Set factory2D1 = sketch1.OpenEdition()

Set geometricElements1 = sketch1.GeometricElements

Set axis2D1 = geometricElements1.Item("Absolute Achse")

Set line2D1 = axis2D1.GetItem("H-Richtung")

line2D1.ReportName = 1

Set line2D2 = axis2D1.GetItem("V-Richtung")

line2D2.ReportName = 2

Set point2D1 = factory2D1.CreatePoint(0.000000, -3.273226)

point2D1.ReportName = 3

Set point2D2 = factory2D1.CreatePoint(0.000000, 13.063307)

point2D2.ReportName = 4

Set line2D3 = factory2D1.CreateLine(0.000000, -3.273226, 0.000000, 13.063307)

line2D3.ReportName = 5

line2D3.StartPoint = point2D1

line2D3.EndPoint = point2D2

Set point2D3 = factory2D1.CreatePoint(5.000000, 0.000000)

point2D3.ReportName = 6

Set line2D4 = factory2D1.CreateLine(0.000000, 0.000000, 5.000000, 0.000000)

line2D4.ReportName = 7

Set point2D4 = axis2D1.GetItem("Ursprung")

line2D4.StartPoint = point2D4

line2D4.EndPoint = point2D3

Set point2D5 = factory2D1.CreatePoint(9.600000, 6.200000)

point2D5.ReportName = 8

Set line2D5 = factory2D1.CreateLine(5.000000, 0.000000, 9.600000, 6.200000)

line2D5.ReportName = 9

line2D5.StartPoint = point2D3

line2D5.EndPoint = point2D5

Set point2D6 = factory2D1.CreatePoint(0.000000, 6.200000)

point2D6.ReportName = 10

Set line2D6 = factory2D1.CreateLine(9.600000, 6.200000, 0.000000, 6.200000)

line2D6.ReportName = 11

line2D6.StartPoint = point2D5

line2D6.EndPoint = point2D6

Set line2D7 = factory2D1.CreateLine(0.000000, 6.200000, 0.000000, 0.000000)

line2D7.ReportName = 12

line2D7.StartPoint = point2D6

line2D7.EndPoint = point2D4

Set constraints1 = sketch1.Constraints

Set reference2 = part1.CreateReferenceFromObject(point2D1)

Set reference3 = part1.CreateReferenceFromObject(line2D2)

Set constraint1 = constraints1.AddBiEltCst(catCstTypeOn, reference2, reference3)

constraint1.Mode = catCstModeDrivingDimension

Set reference4 = part1.CreateReferenceFromObject(line2D3)

Set reference5 = part1.CreateReferenceFromObject(line2D2)

Set constraint2 = constraints1.AddBiEltCst(catCstTypeVerticality, reference4, reference5)

constraint2.Mode = catCstModeDrivingDimension

Set reference6 = part1.CreateReferenceFromObject(line2D4)

Set reference7 = part1.CreateReferenceFromObject(line2D1)

Set constraint3 = constraints1.AddBiEltCst(catCstTypeHorizontality, reference6, reference7)

constraint3.Mode = catCstModeDrivingDimension

Set reference8 = part1.CreateReferenceFromObject(point2D6)

Set reference9 = part1.CreateReferenceFromObject(line2D3)

Set constraint4 = constraints1.AddBiEltCst(catCstTypeOn, reference8, reference9)

constraint4.Mode = catCstModeDrivingDimension

Set reference10 = part1.CreateReferenceFromObject(line2D6)

Set reference11 = part1.CreateReferenceFromObject(line2D1)

Set constraint5 = constraints1.AddBiEltCst(catCstTypeHorizontality, reference10, reference11)

constraint5.Mode = catCstModeDrivingDimension

Set reference12 = part1.CreateReferenceFromObject(line2D7)

Set reference13 = part1.CreateReferenceFromObject(line2D2)

Set constraint6 = constraints1.AddBiEltCst(catCstTypeVerticality, reference12, reference13)

constraint6.Mode = catCstModeDrivingDimension

Set reference14 = part1.CreateReferenceFromObject(line2D6)

Set constraint7 = constraints1.AddMonoEltCst(catCstTypeLength, reference14)

constraint7.Mode = catCstModeDrivingDimension

Set length1 = constraint7.Dimension

length1.Value = 9.600000

Set reference15 = part1.CreateReferenceFromObject(line2D4)

Set constraint8 = constraints1.AddMonoEltCst(catCstTypeLength, reference15)

constraint8.Mode = catCstModeDrivingDimension

Set length2 = constraint8.Dimension

length2.Value = 5.000000

Set reference16 = part1.CreateReferenceFromObject(line2D7)

Set constraint9 = constraints1.AddMonoEltCst(catCstTypeLength, reference16)

constraint9.Mode = catCstModeDrivingDimension

Set length3 = constraint9.Dimension

length3.Value = 6.200000

sketch1.CenterLine = line2D3

sketch1.CloseEdition 

part1.InWorkObject = hybridBody1

part1.Update 

Set bodies1 = part1.Bodies

Set body1 = bodies1.Item("Hauptkörper")

part1.InWorkObject = body1

Set shapeFactory1 = part1.ShapeFactory

Set shaft1 = shapeFactory1.AddNewShaft(sketch1)

Set parameters1 = part1.Parameters

Set length4 = parameters1.Item("Senkkopf\Hauptkörper\Welle.1\ThickThin1")

length4.Value = 1.000000

Set parameters2 = part1.Parameters

Set length5 = parameters2.Item("Senkkopf\Hauptkörper\Welle.1\ThickThin2")

length5.Value = 0.000000

part1.Update 

Set sketches2 = body1.Sketches

Set reference17 = part1.CreateReferenceFromName("Selection_RSur:(Face:(Brp:(Shaft.1;0:(Brp:(Sketch.2;11)));None:();Cf12:());Shaft.1_ResultOUT;Z0;G9061)")

Set sketch2 = sketches2.Add(reference17)

Dim arrayOfVariantOfDouble2(8)
arrayOfVariantOfDouble2(0) = 0.000000
arrayOfVariantOfDouble2(1) = 0.000000
arrayOfVariantOfDouble2(2) = 6.200000
arrayOfVariantOfDouble2(3) = 1.000000
arrayOfVariantOfDouble2(4) = 0.000000
arrayOfVariantOfDouble2(5) = 0.000000
arrayOfVariantOfDouble2(6) = 0.000000
arrayOfVariantOfDouble2(7) = 1.000000
arrayOfVariantOfDouble2(8) = 0.000000
sketch2.SetAbsoluteAxisData arrayOfVariantOfDouble2

part1.InWorkObject = sketch2

Set factory2D2 = sketch2.OpenEdition()

Set geometricElements2 = sketch2.GeometricElements

Set axis2D2 = geometricElements2.Item("Absolute Achse")

Set line2D8 = axis2D2.GetItem("H-Richtung")

line2D8.ReportName = 1

Set line2D9 = axis2D2.GetItem("V-Richtung")

line2D9.ReportName = 2

Set point2D7 = factory2D2.CreatePoint(0.000000, -3.000000)

point2D7.ReportName = 3

Set circle2D1 = factory2D2.CreateClosedCircle(0.000000, 0.000000, 3.464102)

Set point2D8 = axis2D2.GetItem("Ursprung")

circle2D1.CenterPoint = point2D8

circle2D1.ReportName = 4

circle2D1.Construction = True

Set circle2D2 = factory2D2.CreateClosedCircle(0.000000, 0.000000, 3.000000)

circle2D2.CenterPoint = point2D8

circle2D2.ReportName = 5

circle2D2.Construction = True

Set point2D9 = factory2D2.CreatePoint(-1.732051, -3.000000)

point2D9.ReportName = 6

Set point2D10 = factory2D2.CreatePoint(1.732051, -3.000000)

point2D10.ReportName = 7

Set point2D11 = factory2D2.CreatePoint(3.464102, 0.000000)

point2D11.ReportName = 8

Set point2D12 = factory2D2.CreatePoint(1.732051, 3.000000)

point2D12.ReportName = 9

Set point2D13 = factory2D2.CreatePoint(-1.732051, 3.000000)

point2D13.ReportName = 10

Set point2D14 = factory2D2.CreatePoint(-3.464102, 0.000000)

point2D14.ReportName = 11

Set line2D10 = factory2D2.CreateLine(-1.732051, -3.000000, 1.732051, -3.000000)

line2D10.ReportName = 12

line2D10.StartPoint = point2D9

line2D10.EndPoint = point2D10

Set line2D11 = factory2D2.CreateLine(1.732051, -3.000000, 3.464102, 0.000000)

line2D11.ReportName = 13

line2D11.StartPoint = point2D10

line2D11.EndPoint = point2D11

Set line2D12 = factory2D2.CreateLine(3.464102, -0.000000, 1.732051, 3.000000)

line2D12.ReportName = 14

line2D12.StartPoint = point2D11

line2D12.EndPoint = point2D12

Set line2D13 = factory2D2.CreateLine(1.732051, 3.000000, -1.732051, 3.000000)

line2D13.ReportName = 15

line2D13.StartPoint = point2D12

line2D13.EndPoint = point2D13

Set line2D14 = factory2D2.CreateLine(-1.732051, 3.000000, -3.464102, 0.000000)

line2D14.ReportName = 16

line2D14.StartPoint = point2D13

line2D14.EndPoint = point2D14

Set line2D15 = factory2D2.CreateLine(-3.464102, 0.000000, -1.732051, -3.000000)

line2D15.ReportName = 17

line2D15.StartPoint = point2D14

line2D15.EndPoint = point2D9

Set line2D16 = factory2D2.CreateLine(0.000000, 0.000000, 0.000000, -3.000000)

line2D16.ReportName = 18

line2D16.Construction = True

line2D16.StartPoint = point2D8

line2D16.EndPoint = point2D7

Set constraints2 = sketch2.Constraints

Set reference18 = part1.CreateReferenceFromObject(circle2D1)

Set reference19 = part1.CreateReferenceFromObject(point2D9)

Set constraint10 = constraints2.AddBiEltCst(catCstTypeOn, reference18, reference19)

constraint10.Mode = catCstModeDrivingDimension

Set reference20 = part1.CreateReferenceFromObject(circle2D1)

Set reference21 = part1.CreateReferenceFromObject(point2D10)

Set constraint11 = constraints2.AddBiEltCst(catCstTypeOn, reference20, reference21)

constraint11.Mode = catCstModeDrivingDimension

Set reference22 = part1.CreateReferenceFromObject(circle2D1)

Set reference23 = part1.CreateReferenceFromObject(point2D11)

Set constraint12 = constraints2.AddBiEltCst(catCstTypeOn, reference22, reference23)

constraint12.Mode = catCstModeDrivingDimension

Set reference24 = part1.CreateReferenceFromObject(circle2D1)

Set reference25 = part1.CreateReferenceFromObject(point2D12)

Set constraint13 = constraints2.AddBiEltCst(catCstTypeOn, reference24, reference25)

constraint13.Mode = catCstModeDrivingDimension

Set reference26 = part1.CreateReferenceFromObject(circle2D1)

Set reference27 = part1.CreateReferenceFromObject(point2D13)

Set constraint14 = constraints2.AddBiEltCst(catCstTypeOn, reference26, reference27)

constraint14.Mode = catCstModeDrivingDimension

Set reference28 = part1.CreateReferenceFromObject(circle2D1)

Set reference29 = part1.CreateReferenceFromObject(point2D14)

Set constraint15 = constraints2.AddBiEltCst(catCstTypeOn, reference28, reference29)

constraint15.Mode = catCstModeDrivingDimension

Set reference30 = part1.CreateReferenceFromObject(circle2D2)

Set reference31 = part1.CreateReferenceFromObject(line2D10)

Set constraint16 = constraints2.AddBiEltCst(catCstTypeTangency, reference30, reference31)

constraint16.Mode = catCstModeDrivingDimension

Set reference32 = part1.CreateReferenceFromObject(circle2D2)

Set reference33 = part1.CreateReferenceFromObject(line2D11)

Set constraint17 = constraints2.AddBiEltCst(catCstTypeTangency, reference32, reference33)

constraint17.Mode = catCstModeDrivingDimension

Set reference34 = part1.CreateReferenceFromObject(circle2D2)

Set reference35 = part1.CreateReferenceFromObject(line2D12)

Set constraint18 = constraints2.AddBiEltCst(catCstTypeTangency, reference34, reference35)

constraint18.Mode = catCstModeDrivingDimension

Set reference36 = part1.CreateReferenceFromObject(circle2D2)

Set reference37 = part1.CreateReferenceFromObject(line2D13)

Set constraint19 = constraints2.AddBiEltCst(catCstTypeTangency, reference36, reference37)

constraint19.Mode = catCstModeDrivingDimension

Set reference38 = part1.CreateReferenceFromObject(circle2D2)

Set reference39 = part1.CreateReferenceFromObject(line2D14)

Set constraint20 = constraints2.AddBiEltCst(catCstTypeTangency, reference38, reference39)

constraint20.Mode = catCstModeDrivingDimension

Set reference40 = part1.CreateReferenceFromObject(circle2D2)

Set reference41 = part1.CreateReferenceFromObject(line2D15)

Set constraint21 = constraints2.AddBiEltCst(catCstTypeTangency, reference40, reference41)

constraint21.Mode = catCstModeDrivingDimension

Set reference42 = part1.CreateReferenceFromObject(point2D7)

Set reference43 = part1.CreateReferenceFromObject(line2D10)

Set constraint22 = constraints2.AddBiEltCst(catCstTypeMidPoint, reference42, reference43)

constraint22.Mode = catCstModeDrivingDimension

Set reference44 = part1.CreateReferenceFromObject(line2D16)

Set reference45 = part1.CreateReferenceFromObject(line2D9)

Set constraint23 = constraints2.AddBiEltCst(catCstTypeVerticality, reference44, reference45)

constraint23.Mode = catCstModeDrivingDimension

Set reference46 = part1.CreateReferenceFromObject(circle2D2)

Set constraint24 = constraints2.AddMonoEltCst(catCstTypeRadius, reference46)

constraint24.Mode = catCstModeDrivingDimension

Set length6 = constraint24.Dimension

length6.Value = 3.000000

sketch2.CloseEdition 

part1.InWorkObject = sketch2

part1.Update 

Set pocket1 = shapeFactory1.AddNewPocket(sketch2, 20.000000)

Set limit1 = pocket1.FirstLimit

Set length7 = limit1.Dimension

length7.Value = 4.000000

part1.Update 

End Sub
